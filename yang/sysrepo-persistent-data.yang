module sysrepo-persistent-data {

  yang-version 1;

  namespace "urn:ietf:params:xml:ns:yang:sysrepo-persistent-data";

  prefix srpd;

  organization "sysrepo.org";

  contact
    "sysrepo-devel@sysrepo.org";

  description
    "Persistent data that sysrepo stores for each data module. Used only
      internally by Sysrepo Engine.";

  revision "2016-03-30" {
    description "initial revision";
    reference "sysrepo.org";
  }

  identity subscription-type {
    description "Type of the subscription to a YANG module enabled in sysrepo.";
  }

  identity module-install {
    base subscription-type;
    description "Subscription for events triggered by installation or
      uninstallation of a YANG module in sysrepo.";
  }

  identity feature-enable {
    base subscription-type;
    description "Subscription for events triggered by enabling or disabling of
      a feature within a YANG module in sysrepo.";
  }

  identity module-change {
    base subscription-type;
    description "Subscription for events triggered by a change in subscribed
      YANG module.";
  }

  identity subtree-change {
    base subscription-type;
    description "Subscription for events triggered by a change in subscribed
      YANG subtree.";
  }

  identity dp-get-items {
    base subscription-type;
    description "Get-items operational data provider subscription.";
  }

  identity rpc {
    base subscription-type;
    description "Subscription for delivery of RPC identified by xpath.";
  }

  identity action {
    base subscription-type;
    description "Subscription for delivery of action (YANG 1.1) identified by xpath.";
  }

  identity event-notification {
    base subscription-type;
    description "Subscription for delivery of event notification (RFC 5277) identified by xpath.";
  }

  identity notification-event {
    description "Notification event which the subscriber is interested in.";
  }

  identity verify {
    base notification-event;
    description "Occurs just before the changes are committed to the datastore.";
  }

  identity notify {
    base notification-event;
    description "Occurs just after the changes have been committed to the datastore.";
  }

  list module {
    key "name";
    description "Module-specific persistent data maintained by sysrepo.";

    leaf name {
      type string;
      description "Name of the YANG module.";
    }

    container enabled-features {
      description "Features of the YANG module that are currently enabled in
        sysrepo.";

      leaf-list feature-name {
        type string;
        description "Name of a feature that is currently enabled in sysrepo.";
      }
    }

    container subscriptions {
      description "Active notification subscriptions of a module.";

      list subscription {
        key "type destination-address destination-id";
        description "A subscription instance.";

        leaf type {
          type identityref {
            base subscription-type;
          }
          description "Type of the subscription.";
        }

        leaf destination-address {
          type string;
          description "Destination address for notification delivery.";
        }

        leaf destination-id {
          type uint32;
          description "Destination-local subscription identifier.";
        }

        leaf xpath {
          when "../type = 'subtree-change' or ../type = 'dp-get-items' or ../type = 'rpc' " +
               "or ../type = 'action' or ../type = 'event-notification'";
          type string;
          description "XPath of the subtree where the subscription is active.";
        }

        leaf event {
          when "../type = 'module-change' or ../type = 'subtree-change'";
          type identityref {
            base notification-event;
          }
          description "Notification event which the subscriber is interested in.";
        }

        leaf priority {
          when "../type = 'module-change' or ../type = 'subtree-change'";
          type uint32;
          description "Priority of the subscribtion by delivering notifications (0 is the lowest priority).";
        }

        leaf enable-running {
          when "../type = 'module-change' or ../type = 'subtree-change' or ../type = 'dp-get-items'";
          type empty;
          description "If present, the subscription enables specified subtree in
            the running datastore.";
        }
      }
    }
  }
}
