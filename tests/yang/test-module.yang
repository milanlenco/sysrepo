module test-module {
  namespace "urn:ietf:params:xml:ns:yang:test-module";
  prefix tm;

  import ietf-inet-types {
    prefix inet;
  }

  organization "organization";
  description
    "example yang module";
  contact
    "example@example.org";

  container main {
    leaf enum {
      type enumeration {
        enum "yes" {
          value 1;
        }
        enum "no" {
          value 2;
        }
        enum "maybe" {
          value 3;
        }
      }
    }
    leaf options {
      type bits {
        bit strict;
        bit recursive;
        bit logging;
      }
    }
    leaf raw {
      type binary;
    }
    leaf dec64 {
      type decimal64{
         fraction-digits 2;
      }
    }
    leaf i8 {
      type int8;
    }
    leaf i16 {
      type int16;
    }
    leaf i32 {
      type int32;
    }
    leaf i64 {
      type int64;
    }
    leaf ui8 {
      type uint8;
    }
    leaf ui16 {
      type uint16;
    }
    leaf ui32 {
      type uint32;
    }
    leaf ui64 {
      type uint64;
    }
    leaf empty {
      type empty;
    }
    leaf boolean {
      type boolean;
    }
    leaf string {
      type string;
    }
    leaf id_ref {
      type identityref{
        base base_id;
      }
    }
    leaf-list numbers {
      type uint8;
    }
  }

  identity base_id;

  identity id_1 {
    base base_id;
  }

  identity id_2 {
    base base_id;
  }

  list list {
    key "key";
    leaf key {
      type string;
    }
    leaf id_ref {
      type identityref{
        base base_id;
      }
    }
    leaf union {
      type union{
          type uint8;
          type enumeration {
              enum "infinity";
          }
      }
    }
    container wireless{
        presence "wireless is enabled";
        leaf vendor_name{
          type string;
        }
    }
  }

  container transfer {
    choice how {
        default interval;
        case interval {
            leaf interval {
                type uint16;
                default 30;
                units minutes;
            }
        }
        case daily {
            leaf daily {
                type empty;
            }
            leaf time-of-day {
                type string;
                units 24-hour-clock;
                default 1am;
            }
        }
        case manual {
            leaf manual {
                type empty;
            }
        }
    }
  }

  container location {
    presence true;
    leaf name {
        type string;
    }

    leaf longitude {
        type string;
        mandatory true;
    }

    leaf latitude {
        type string;
        mandatory true;
    }
  }

  leaf hexnumber{
    type string {
            length "0..4";
            pattern "[0-9a-fA-F]*";
        }
  }

  container interface {
    leaf ifType {
        type enumeration {
          enum ethernet;
            enum atm;
        }
    }
    leaf ifMTU {
        type uint32;
    }
    must "ifType != 'ethernet' or " +
         "(ifType = 'ethernet' and ifMTU = 1500)" {
         error-message "An ethernet MTU must be 1500";
    }
    must "ifType != 'atm' or " +
         "(ifType = 'atm' and ifMTU <= 17966 and ifMTU >= 64)" {
         error-message "An atm MTU must be  64 .. 17966";
    }
 }

  list user {
    description "This is a list of users in the system.";
    ordered-by user;
    config true;

    key "name";

    leaf name {
        type string;
    }
    leaf type {
        type string;
    }
    leaf full-name {
        type string;
    }
  }

  leaf-list ordered-numbers {
    ordered-by user;
    type uint8;
  }

  list with_def {
    config true;
    key "name";
    leaf name {
        type string;
    }
    leaf num {
        type int8;
        default 0;
    }
  }

  rpc activate-software-image {
    input {
      leaf image-name {
        type string;
      }
      leaf location {
        type string;
        default "/";
      }
    }
    output {
      leaf status {
        type string;
      }
      leaf version {
        type string;
      }
      leaf location {
        type string;
        default "/";
      }
    }
  }

  leaf top-level-default {
    type string;
    default "default value";
  }

  container university {
    container students {
        list student {
            ordered-by user;
            config true;

            key "name";

            leaf name {
                type string;
            }

            leaf age {
                type uint8;
            }
        }
    }

    container classes {
        list class {
            config true;

            key "title";

            leaf title {
                type string;
            }

            list student {
                key "name";

                leaf name {
                    type leafref {
                        path "../../../../students/student/name";
                    }
                }
                leaf age {
                    type leafref {
                        path "../../../../students/student[name = current()/../name]/age";
                    }
                }
            }
        }
    }
  }

  container leafref-chain {
    leaf A {
        type leafref {
            path "../B";
        }
    }

    leaf B {
        type leafref {
            path "../C";
        }
    }

    leaf C {
        type leafref {
            path "../D";
        }
    }

    leaf D {
        type string;
    }
  }

  grouping link {
    container source {
      leaf address {
        type inet:ipv4-address;
      }
      leaf interface {
        type string;
      }
    }
    container destination {
      leaf address {
        type inet:ipv4-address;
      }
      leaf interface {
        type string;
      }
    }
    leaf MTU {
      type uint16;
      default 1500;
    }
  }

  notification link-discovered {
    uses link;
  }

  notification link-removed {
    uses link;
  }

  container kernel-modules {
    list kernel-module {
      key "name";

      leaf name {
        type string;
      }

      leaf location {
        type string;
        default "/lib/modules";
      }

      leaf loaded {
        type boolean;
      }

      action load {
        input {
          leaf params {
            mandatory "true";
            type string;
          }
          leaf force {
            type boolean;
            default "false";
          }
          leaf dry-run {
            type boolean;
            default false;
          }
        }
        output {
          leaf return-code {
            type uint8;
          }
        }
      }

      action get-dependencies {
        output {
          leaf-list dependency {
            type string;
          }
        }
      }

      notification status-change {
        leaf loaded {
          type boolean;
        }
        leaf time-of-change {
          type uint32;
        }
      }
    }
  }

}
